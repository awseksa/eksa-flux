module mavenir-cnp-fmaas-config {
	namespace "urn:mavenir:ns:yang:cnp:mtcil:fmaas";

	prefix mtcil-fmaas;

	import ietf-inet-types { prefix inet; }

        import tailf-common { prefix tailf; }

	revision "2019-02-19" {
		description "Initial revision";
	}
	container config {
		tailf:callpoint configUpdate {
			tailf:transaction-hook subtree;
		}
		leaf log_level {
			type enumeration {
				enum INFO;
				enum DEBUG;
				enum ERROR;
				enum WARNING;
				enum EXCEPTION;
				enum ALL;
			}
			default INFO;
			description "Log Level for fmaas to print. select all if want to print all levels.";
		}
		leaf dataRetentionPeriod {
			type int32 {
				range "0 .. 365";
			}
			mandatory true;
			description "Data retention period in days";
		}
		list collectorDetails {
			key id;
			leaf id {
				type int32 {
					range "1 .. 20";
				}
				description "Id for VES Collector ";
			}
			list ruleList {
				key id;
				leaf id {
					type int32 {
						range "1 .. 20";
					}
					description "Rule Id for the corresponding collector Id(As same collector can have multiple rules.)";
				}
				leaf name {
					type string;
					description "rule Name.";
					mandatory  true;
				}
				leaf description {
					type string;
					description "rule Description.";
					mandatory  false;
				}
				leaf action {
					type enumeration {
						enum allow;
						enum block;
					}
					default allow;
					description "rule action.";
				}
				leaf status {
					type enumeration {
						enum enabled;
						enum disabled;
					}
					default enabled;
					description "rule Status.";
				}
				list ruleDetails {
					key ruleId;
					leaf ruleId {
						type int32 {
							range "1 .. 50";
						}
						description "Condition Id for the corresponding rule Id(As same rule can have multiple Conditions.)";
					}
					leaf ruleName {
						type string;
						description "rule Name.";
						mandatory  false;
					}
					leaf ruleDescription {
						type string;
						description "rule description.";
						mandatory  false;
					}
					container rule {
						leaf field {
							type enumeration {
								enum domain;
								enum eventName;
								enum eventType;
								enum nfNamingCode;
								enum nfcNamingCode;
								enum reportingEntityName;
								enum sourceName;
								enum custom;
							}
							description "field to form the rule";
							mandatory  true;
						}
						leaf customField {
							type "string";
							description "Please provide custom field name along with path, it will be considered if field is set to custom, else ignored.";
							mandatory  false;
						}
						leaf value {
							type "string";
							description "Value for the field selected in previous field option.";
							mandatory  true;
						}
						leaf compareOper {
							type enumeration {
								enum ==;
								enum !=;
								enum Contains;
								enum NotContains;
								enum In;
								enum NotIn;
							}
							description "field value relational operator.";
							mandatory  true;
						}
						leaf status {
							type enumeration {
								enum enabled;
								enum disabled;
							}
							default enabled;
							description "field value relational operator.";
						}
					}
					leaf ruleOper {
						type enumeration {
							enum &&;
							enum ||;
						}
						description "Conditional operator between two rules, Along with last rule no need to configure, If configured also will be ignored as part of creating the rule.";
					}
				}
			}
			container primaryCollector {
				leaf fqdn {
					type string;
					description "fqdn for collector";
				}
				leaf port {
					type int32 {
							range "6000 .. 65506";
					}
					description "port for collector";
				}
				leaf secure {
					type boolean;
					description "establish a secure connection from vesgw to collector";
				}
				leaf user {
					type string;
					description "username for establishing secure connection";
				}
				leaf password {
					type string;
					description "password to establish secure connection";
				}
				leaf passphrase {
					type string;
					description "passphrase for connection between vesgw and collector";
				}
				leaf nbiFormat {
					type enumeration {
							enum VES;
							enum RCP;
					}
					description "nbiFormat to set RCP or VES format";
				}
				leaf nbiType {
					type enumeration {
							enum REST;
							enum KAFKA;
					}
					description "nbiType to set REST or KAFKA endpoint";
				}
				leaf-list kafkaBrokers {
					type string;
					description "List of kafka brokers as url:port.";
				}
				leaf kafkaTopic {
					type string;
					description "kafka topic";
				}
				leaf heartbeat {
					type boolean;
					description "Send Heartbeat to collector";
					mandatory  true;
				}
			}

			container backupCollector{
					leaf fqdn {
							type string;
							description "fqdn for collector";
					}
					leaf port {
							type int32 {
									range "6000 .. 65506";
							}
							description "port for collector";
					}
					leaf secure {
							type boolean;
							description "establish a secure connection from vesgw to collector";
					}
					leaf user {
							type string;
							description "username for establishing secure connection";
					}
					leaf password {
							type string;
							description "password to establish secure connection";
					}
					leaf passphrase {
							type string;
							description "passphrase for connection between vesgw and collector";
					}
					leaf nbiFormat {
							type enumeration {
									enum VES;
									enum RCP;
							}
							description "nbiFormat to set RCP or VES format";
					}
					leaf nbiType {
							type enumeration {
									enum REST;
									enum KAFKA;
							}
							description "nbiType to set REST or KAFKA endpoint";
					}
					leaf-list kafkaBrokers {
							type string;
							description "List of kafka brokers as url:port.";
					}
					leaf kafkaTopic {
							type string;
							description "kafka topic";
					}
					leaf heartbeat {
							type boolean;
							description "Send Heartbeat to collector";
					}
			}
        }
		container vesdomains {
			container fault {
				list collectorList{
					key id;
					leaf id {
						type int32 {
							range "1 .. 20";
						}
						description "Ids of VES Collector to which faults are configured ";
					}
				}
			}
			container measurement {
				list collectorList{
					key id;
					leaf id {
						type int32 {
							range "1 .. 20";
						}
						description "Ids of VES Collector to which measurements are configured  ";
					}
				}
			}
			container notification {
				list collectorList{
					key id;
					leaf id {
						type int32 {
							range "1 .. 20";
						}
						description "Ids of VES Collector to which notifications are configured  ";
					}
				}
			}
			container tca {
				list collectorList{
					key id;
					leaf id {
						type int32 {
							range "1 .. 20";
						}
						description "Ids of VES Collector to which tcas are configured ";
					}
				}
			}
		}
		container heartbeat {
			leaf defaultInterval {
				type string;
				mandatory true;
				description "Default interal configured for heartbeat to collectors";
			}
		}
		container measurement {
			leaf defaultInterval {
				type string;
				mandatory true;
				description "Default interal configured for measurement to collectors";
			}
			leaf maxBufferingDuration {
				type string;
				mandatory true;
				description "";
			}
			container prometheus {
				leaf address {
					type string;
					mandatory true;
					description "Prometheus server address for measurement";
				}
				leaf timeout {
					type string;
					mandatory true;
					description "";
				}
				leaf keepalive {
					type string;
					mandatory true;
					description "";
				}
			}
		}
		container event {
			leaf maxSize {
				type int32 {
					range "1 .. 3000000";
				}
				mandatory true;
				description "";
			}
			leaf retryInterval {
				type string;
				mandatory true;
				description "";
			}
			leaf maxMissed {
				type int32 {
					range "1 .. 200";
				}
				mandatory true;
				description "";
			}
		}
		container alertManager {
			leaf bind {
				type string;
				mandatory true;
				description "";
			}
		}
		container cluster {
			leaf debug {
				type boolean;
				mandatory true;
				description "";
			}
			leaf displayLogs {
				type boolean;
				mandatory true;
				description "";
			}
		}
	}
}
